module odlexample {
    yang-version 1;
    namespace "urn:opendaylight:params:xml:ns:yang:odlexample";
    prefix "odlexample";

    revision "2015-01-05" {
        description "Initial revision of odlexample model";
    }
    
    rpc startFailover {
        input{
            leaf srcNode {
                type string;
            }
            leaf dstNode {
                type string;
            }
        }
    }

    typedef ApplicationType {
        type enumeration {
            enum "VoIP";
            enum "Video";
        }
    }

    rpc startMonitoringLinks{
        input{
            leaf srcNode {
                type string;
            }
            leaf dstNode {
                type string;
            }
            leaf QoEThreshold {
                type string;
            }
            leaf application {
                type ApplicationType;
            }
        }
    }

    rpc stopMonitoringLinks{

    }

}
