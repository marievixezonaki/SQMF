module sqmf {
    yang-version 1;
    namespace "urn:opendaylight:params:xml:ns:yang:sqmf";
    prefix "sqmf";

    revision "2014-12-10" {
        description "Initial revision of sqmf model";
    }
    
 /*   rpc startFailover {
        input{
            leaf srcNode {
                type string;
            }
            leaf dstNode {
                type string;
            }
        }
    }*/

    typedef ApplicationType {
        type enumeration {
            enum "VoIP";
            enum "UDP Video";
            enum "Web Based Video";
        }
    }

    rpc startMonitoringLinks{
        input{
            leaf srcNode {
                type string;
            }
            leaf dstNode {
                type string;
            }
            leaf QoEThreshold {
                type string;
            }
            leaf application {
                type ApplicationType;
            }
        }
    }

    rpc stopMonitoringLinks{

    }

}
